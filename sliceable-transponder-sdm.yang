module sliceable-transponder-sdm {

  namespace "urn:sliceable-transponder-sdm";

  prefix "sliceable-transponder-sdm";

  organization
    "CTTC";

  contact
    "ricard.vilalta@cttc.es";

  description
    "Latest update to sliceable transponder SDM YANG data model.";

  revision "2017-03-10" {
    description "Update to  sliceable transponder SDM YANG data model initial revision.";
    reference "";
  }
  
  identity constelation {
    description "constelation base";
  }
  
  identity "qam64" {
    base constelation;
  }
  
  /** ADD MORE*/

  grouping frequency-slot {
    leaf ncm {
      type int32;
      description "Nominal central frequency = 193.1 THz + n x 0.00625 THz. 
                  where 193.1 THz is ITU-T anchor frequency for transmission 
                  over the C band, and n is a positive or negative integer including 0.";
    }
    leaf slot-width {
      type uint32;
      description "Slot width = m x 12.5 GHz, where m is an integer greater than or equal to 1.";
    }
    leaf constelation {
      type identityref {
        base constelation;
      }
    }
    leaf baudrate {
      type decimal64 {
         fraction-digits 2;
      }
    }
    leaf fec {
      type string;
    }
  }

  grouping wavelength {
    leaf wavelength-id {
      type string;
    }
    container frequency-slot {
      uses frequency-slot;
    }
    
  }

  grouping mode {
    leaf mode-id {
      type string;
    }
    leaf mode {
      type string;
      description "e.g. lp01";
    }
    list wavelength {
      key "wavelength-id";
      uses wavelength;
    }
  }

  grouping core {
    leaf core-id {
      type string;
    }
    list mode {
      key "mode-id";
      uses mode;
    }
  }

  grouping slice {
    leaf slice-id {
      type string;
    }
    list core {
      key "core-id";
      uses core;
    }
  }

  grouping transponder {
    list slice{
      key "slice-id";
      uses slice;
    }
  
  }

  /**
   * Container/lists
   */
  
  container transponder {
    uses transponder;
  } 

}
